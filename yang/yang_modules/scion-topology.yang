module scion-topology {
    yang-version 1.1;
    namespace "urn:scion:scion-topology";
    prefix "sc-topo";

    import scion-types{
      prefix "sc-ty";
    }

    import scion-interfaces{
      prefix "sc-if";
    }

    organization
    "SCION group";

    contact
    "Some contact here";

    description 
    "This module contains a collection of data defining the topology
    configuration within the Autonomous System (AS) identified by its
    ISD-AS number.
    ";

    revision 2020-03-15 {
        description "Second revision for proposal.";
    }

    container topology{
      leaf core{
        description "This boolean expresses whether or not this module belongs to the ISD core.";
        type boolean;
        mandatory true;
      }

      leaf isd-as{
        description "The ISD-AS number identifies the AS within the ISD.";
        type sc-ty:isd-as-type;
        mandatory true;
      }

      leaf underlay-proto {
          description "Definition of the underlay protocol protocol used for communication within the AS.";
          mandatory true;
          type identityref {
              base "sc-ty:underlay-proto";
          }
      }

      leaf mtu{
        description "Maximum Transmission Unit within the AS.";
        type uint16;
        mandatory true;
      }

      container attributes{
        leaf-list attribute{
          description "Set of attributes which an AS might have.";
          reference "https://github.com/scionproto/scion/blob/master/doc/ControlPlanePKI.md#primary-ases";

          type identityref{
            base "sc-ty:topology-attribute-base";
          }
        }
      }

      container control-service{
        list control-server{
          key name;
          description 
          "Control server list for the AS.

          Every Control server is uniquely identified within the AS by its 
          name and can be reached at the provided address and port.

          Control server encompasses Beacon, Certifcate and Path services.
          ";
            
          leaf name{
            type string;
          }
          uses sc-ty:address-port;

          must ' not(derived-from(/topology/underlay-proto, "sc-ty:underlay-proto-ipv4")) or
                 re-match(current()/address,"(([0-9]|[1-9][0-9]|1[0-9][0-9]|2[0-4][0-9]|25[0-5])\.){3}([0-9]|[1-9][0-9]|1[0-9][0-9]|2[0-4][0-9]|25[0-5])")'
          {
                  error-message "No match between underlay-proto and address format";
          }

          must ' not(derived-from(/topology/underlay-proto, "sc-ty:underlay-proto-ipv6")) or
                 re-match(current()/address,"((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))")'
          {
                  error-message "No match between underlay-proto and public-underlay address format";
          }
        }
      }

      container sig{
        list sig-instance{
          key name;
          description 
          "SCION IP Gateway (SIG) instance list for the AS.

          Every SIG instance enables legacy IP applications to communicate over SCION.
          ";
            
          leaf name{
            type string;
          }
          uses sc-ty:address-port;

          must ' not(derived-from(/topology/underlay-proto, "sc-ty:underlay-proto-ipv4")) or
                 re-match(current()/address,"(([0-9]|[1-9][0-9]|1[0-9][0-9]|2[0-4][0-9]|25[0-5])\.){3}([0-9]|[1-9][0-9]|1[0-9][0-9]|2[0-4][0-9]|25[0-5])")'
          {
                  error-message "No match between underlay-proto and address format";
          }

          must ' not(derived-from(/topology/underlay-proto, "sc-ty:underlay-proto-ipv6")) or
                 re-match(current()/address,"((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))")'
          {
                  error-message "No match between underlay-proto and public-underlay address format";
          }
        }
      }

      container border-routers{
        list border-router{
          key name;
          description 
          "Border router list for the AS. 

          Every Border router is identified by its name. Every instance must
          define two addresses, one control address and one internal-address.
          ";
          leaf name{
            type string;
          }

          container control-address{
            description
            "
            The control address is used to send control-plane traffic to 
            the border router from inside the AS.
            ";
            uses sc-ty:address-port;

            must ' not(derived-from(/topology/underlay-proto, "sc-ty:underlay-proto-ipv4")) or
                   re-match(current()/address,"(([0-9]|[1-9][0-9]|1[0-9][0-9]|2[0-4][0-9]|25[0-5])\.){3}([0-9]|[1-9][0-9]|1[0-9][0-9]|2[0-4][0-9]|25[0-5])")'
            {
                    error-message "No match between underlay-proto and address format";
            }

            must ' not(derived-from(/topology/underlay-proto, "sc-ty:underlay-proto-ipv6")) or
                   re-match(current()/address,"((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))")'
            {
                    error-message "No match between underlay-proto and public-underlay address format";
            }
          }

          container internal-address{
            description
            "
            The internal address is used to send data-plane traffic.
            ";
            uses sc-ty:address-port;

            must ' not(derived-from(/topology/underlay-proto, "sc-ty:underlay-proto-ipv4")) or
                   re-match(current()/address,"(([0-9]|[1-9][0-9]|1[0-9][0-9]|2[0-4][0-9]|25[0-5])\.){3}([0-9]|[1-9][0-9]|1[0-9][0-9]|2[0-4][0-9]|25[0-5])")'
            {
                    error-message "No match between underlay-proto and address format";
            }

            must ' not(derived-from(/topology/underlay-proto, "sc-ty:underlay-proto-ipv6")) or
                   re-match(current()/address,"((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))")'
            {
                    error-message "No match between underlay-proto and public-underlay address format";
            }
          }

          uses sc-if:interfaces-top;
          
        }//end list br
      }//end container br
    }
}
